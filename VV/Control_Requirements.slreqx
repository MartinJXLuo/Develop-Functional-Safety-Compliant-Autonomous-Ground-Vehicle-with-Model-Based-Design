# Control

## #1: Emergency Stop Mode (Functional)
The vehicle SHALL transition to Emergency Stop Mode when EmergencyStopEnable is TRUE.

## #2: Remote Control Mode (Functional)
When Path Folloiwng Mode, the vehicle SHALL transition to Remote Control Mode when RomoteControlEnale is TRUE.

## #3: Path Following Mode (Functional)
The vehicle SHALL transition to Path Following Mode when the following conditions are all met:
1. EmergencyStopEnable is FALSE
2. RemoteControlEnable is FALSE
3. CloseToGoal is FALSE
4. PathFollowing is TRUE
